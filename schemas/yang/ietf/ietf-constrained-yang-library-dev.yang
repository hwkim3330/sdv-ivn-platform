// Copyright (c) 2021-2022 Microchip Technology Inc. and its subsidiaries.
//
// Unpublished rights reserved under the copyright laws of the United States
// of America, other countries and international treaties. Permission to use,
// copy, store and modify, the software and its source code is granted but
// only in connection with products utilizing the Microsemi switch and PHY
// products.  Permission is also granted for you to integrate into other
// products, disclose, transmit and distribute the software only in an
// absolute machine readable format (e.g. HEX file) and only in or with
// products utilizing the Microsemi switch and PHY products.  The source code
// of the software may not be disclosed, transmitted or distributed without
// the prior written permission of Microsemi.
//
// This copyright notice must appear in any copy, modification, disclosure,
// transmission or distribution of the software.  Microsemi retains all
// ownership, copyright, trade secret and proprietary rights in the software
// and its source code, including all modifications thereto.
//
// THIS SOFTWARE HAS BEEN PROVIDED "AS IS". MICROSEMI HEREBY DISCLAIMS ALL
// WARRANTIES OF ANY KIND WITH RESPECT TO THE SOFTWARE, WHETHER SUCH
// WARRANTIES ARE EXPRESS, IMPLIED, STATUTORY OR OTHERWISE INCLUDING, WITHOUT
// LIMITATION, WARRANTIES OF MERCHANTABILITY, FITNESS FOR A PARTICULAR USE OR
// PURPOSE AND NON-INFRINGEMENT.

module ietf-constrained-yang-library-dev {
    yang-version 1.1;
    namespace "urn:mchp:params:xml:ns:yang:ietf-constrained-yang-library-dev";
    prefix ietf-constrained-yang-library-dev-pre;

    import ietf-constrained-yang-library {
        prefix yanglib;
    }

    revision 2024-04-12 {
    }

    deviation /yanglib:yang-library-update {
        deviate not-supported;
    }

    deviation /yanglib:yang-library/yanglib:module-set/yanglib:module/yanglib:feature {
        deviate not-supported;
    }

    deviation /yanglib:yang-library/yanglib:module-set/yanglib:module/yanglib:location {
        deviate not-supported;
    }

    deviation /yanglib:yang-library/yanglib:module-set/yanglib:module/yanglib:namespace {
        deviate not-supported;
    }

    deviation /yanglib:yang-library/yanglib:module-set/yanglib:module/yanglib:submodule {
        deviate not-supported;
    }

    deviation /yanglib:yang-library/yanglib:module-set/yanglib:import-only-module/yanglib:namespace {
        deviate not-supported;
    }

    deviation /yanglib:yang-library/yanglib:module-set/yanglib:import-only-module/yanglib:location {
        deviate not-supported;
    }

    deviation /yanglib:yang-library/yanglib:module-set/yanglib:import-only-module/yanglib:submodule {
        deviate not-supported;
    }

}
