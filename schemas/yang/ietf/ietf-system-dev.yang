// Copyright (c) 2021-2022 Microchip Technology Inc. and its subsidiaries.
//
// Unpublished rights reserved under the copyright laws of the United States
// of America, other countries and international treaties. Permission to use,
// copy, store and modify, the software and its source code is granted but
// only in connection with products utilizing the Microsemi switch and PHY
// products.  Permission is also granted for you to integrate into other
// products, disclose, transmit and distribute the software only in an
// absolute machine readable format (e.g. HEX file) and only in or with
// products utilizing the Microsemi switch and PHY products.  The source code
// of the software may not be disclosed, transmitted or distributed without
// the prior written permission of Microsemi.
//
// This copyright notice must appear in any copy, modification, disclosure,
// transmission or distribution of the software.  Microsemi retains all
// ownership, copyright, trade secret and proprietary rights in the software
// and its source code, including all modifications thereto.
//
// THIS SOFTWARE HAS BEEN PROVIDED "AS IS". MICROSEMI HEREBY DISCLAIMS ALL
// WARRANTIES OF ANY KIND WITH RESPECT TO THE SOFTWARE, WHETHER SUCH
// WARRANTIES ARE EXPRESS, IMPLIED, STATUTORY OR OTHERWISE INCLUDING, WITHOUT
// LIMITATION, WARRANTIES OF MERCHANTABILITY, FITNESS FOR A PARTICULAR USE OR
// PURPOSE AND NON-INFRINGEMENT.

module ietf-system-dev {
    yang-version 1.1;
    namespace "urn:mchp:params:xml:ns:yang:ietf-system-dev";
    prefix ietf-system-dev-pre;

    import ietf-system {
        prefix sys;
    }

    revision 2024-04-12 {
    }

    deviation /sys:set-current-datetime {
        deviate not-supported;
    }

    deviation /sys:system-shutdown {
        deviate not-supported;
    }

    deviation /sys:system-state/sys:clock {
        deviate not-supported;
    }

    deviation /sys:system-state/sys:platform/sys:os-name {
        deviate not-supported;
    }

    deviation /sys:system-state/sys:platform/sys:os-release {
        deviate not-supported;
    }

    deviation /sys:system/sys:authentication/sys:user-authentication-order {
        deviate not-supported;
    }

    deviation /sys:system/sys:authentication/sys:user/sys:authorized-key {
        deviate not-supported;
    }

    deviation /sys:system/sys:authentication/sys:user/sys:password {
        deviate not-supported;
    }

    deviation /sys:system/sys:clock {
        deviate not-supported;
    }

    deviation /sys:system/sys:contact {
        deviate not-supported;
    }

    deviation /sys:system/sys:dns-resolver {
        deviate not-supported;
    }

    deviation /sys:system/sys:hostname {
        deviate not-supported;
    }

    deviation /sys:system/sys:location {
        deviate not-supported;
    }

    deviation /sys:system/sys:ntp {
        deviate not-supported;
    }

    deviation /sys:system/sys:radius {
        deviate not-supported;
    }

}
